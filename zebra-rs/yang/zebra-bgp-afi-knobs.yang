module zebra-bgp-afi-knobs {
  yang-version "1";

  namespace "urn:ietf:params:xml:ns:yang:zebra-bgp-afi-knobs";
  prefix "zbak";

  import extension {
    prefix ext;
  }

  organization
    "zebra-rs";

  contact
    "https://github.com/zebra-rs";

  description
    "Per-AFI BGP neighbor knobs shared verbatim by the two neighbor
     subtrees:

       * the global neighbor, /router/bgp/neighbor/afi-safi
         (ietf-bgp-neighbor)
       * the per-VRF CE neighbor, /router/bgp/vrf/neighbor/afi-safi
         (zebra-bgp-vrf)

     A single `grouping` used from both is what makes the two
     definitions the same definition, rather than two copies that agree
     today. The behaviour side is already unified — each knob has one
     setter in src/bgp/afi_knob.rs, called by the global callback (live
     peer) and the per-VRF callback (staged) — and this closes the
     schema side.

     That gap was not theoretical. When these knobs were first imported
     into the per-VRF subtree the leaves were hand-copied, and both
     enum-valued ones came out as `type string`. Nothing caught it in
     review or in CI: `vrf_afi_knob_parity` compares the *set* of knob
     paths, not their types. It surfaced only from a live differential
     probe against the global neighbor, and it mattered because
     `Bgp::process_cm_msg` discards a config callback's return value —
     a setter that rejects a value cannot report it, so the schema type
     is the only thing standing between a typo and a silently ignored
     commit.

     One knob is deliberately NOT here:

       * `graceful-restart` — the global container takes
         `mp-afi-safi-graceful-restart-config`, whose `enabled` leaf
         carries `must \". = ../../../../graceful-restart/enabled\"`.
         That path is anchored to the global neighbor's depth in the
         tree and would be wrong under `vrf/neighbor`. The global
         container also carries `if-feature` and three `config false`
         state leaves the per-VRF one has no use for.

     That exclusion is also recorded, with its reason, in
     VRF_AFI_KNOB_EXCLUSIONS / docs/orphan-report.txt.";

  grouping bgp-neighbor-afi-knobs {
    description
      "Per-address-family knobs common to the global and per-VRF BGP
       neighbor. Semantics are identical on both; what differs is only
       when they take effect — the global neighbor applies them to a
       live peer, while a per-VRF CE peer lives in a separate task, so
       its values are staged and applied when the VRF task next
       respawns (or on `clear bgp`).";

    leaf add-path {
      ext:help "Additional-Paths send/receive mode (RFC 7911)";
      ext:sort "10";
      type enumeration {
        enum send;
        enum receive;
        enum send-receive;
      }
      description
        "Additional-Paths mode for this family. Negotiated in the OPEN,
         so a change takes effect when the session next renegotiates
         capabilities.";
    }

    leaf encapsulation-type {
      ext:help "Encapsulation for advertised routes (srv6)";
      when "../name = 'ipv6'" {
        description
          "SRv6 encapsulation only applies to the IPv6 unicast
           family.

           NOTE: this `when` is documentation, not enforcement — the
           config engine does not evaluate it. `afi-safi ipv4
           encapsulation-type srv6` commits successfully on both the
           global and the per-VRF neighbor. Consumers must therefore
           key the value by family and must not assume IPv6.";
      }
      ext:sort "20";
      type enumeration {
        enum srv6 {
          description
            "SRv6-only peer. Only routes carrying an SRv6 service SID
             (BGP Prefix-SID attribute, RFC 9252) are advertised to /
             accepted from this neighbor; routes without a SID are
             filtered out on the session.";
        }
        enum srv6-relax {
          description
            "Mixed session. Routes with or without an SRv6 service SID
             may be advertised to / accepted from this neighbor.";
        }
      }
      description
        "Per-neighbor SRv6 encapsulation mode for the IPv6 unicast
         family. `srv6` makes the session SRv6-strict (SID-less routes
         filtered), `srv6-relax` SRv6-relaxed (SID-less routes still
         exchanged). Absent = no SRv6 encapsulation filtering for the
         family.";
    }

    leaf next-hop-self {
      ext:help "Advertise self as next hop to this neighbor";
      ext:sort "30";
      type boolean;
      description
        "Advertise our own address as the BGP next-hop for routes sent
         to this neighbor in this address family, even when the route
         was learned from another peer. Equivalent to `neighbor X
         next-hop-self` (per address-family) in FRR / Cisco IOS.

         By default the next-hop is rewritten to self only for eBGP and
         locally-originated routes; a route learned from one iBGP/eBGP
         peer and reflected/forwarded to another keeps its received
         next-hop. Setting this forces next-hop-self on those forwarded
         routes too.

         Required on the iBGP IPv4/IPv6 Labeled-Unicast session an
         Inter-AS MPLS/VPN Option C ASBR runs toward its PE, and on the
         iBGP VPNv4 session an Inter-AS Option B ASBR runs toward its PE:
         the PE must resolve the ASBR's loopback (reachable via the IGP)
         and push the ASBR's swap label, not the unreachable foreign-AS
         next-hop carried across the inter-AS eBGP link. Honored on the
         unicast (SAFI 1), Labeled-Unicast (SAFI 4), and VPNv4 (SAFI 128)
         advertise paths — for unicast it forces self even on an iBGP→iBGP
         (reflected) advertise, unless next-hop-unchanged overrides it.

         Unlike the other knobs here this one is not simply stored: the
         statement is recorded verbatim and the EFFECTIVE value is then
         resolved through neighbor-group precedence
         (`neighbor_group::resolve_next_hop_self`) — explicit statement
         first, else the referenced group's per-family opinion, else
         off. Both subtrees do that resolution, the global neighbor in
         its config callback and the per-VRF neighbor in
         `materialize_peers`.";
    }

    leaf next-hop-unchanged {
      ext:help "Keep the received next hop on eBGP advertisement";
      ext:sort "31";
      type boolean;
      description
        "Advertise routes of this address family to this eBGP neighbor
         with their received next-hop preserved, instead of the default
         eBGP rewrite to self. Equivalent to `neighbor X
         next-hop-unchanged` (per address-family) in FRR / Cisco IOS.

         Required on the multihop eBGP VPNv4 session between the route
         reflectors of an RR-based Inter-AS MPLS/VPN Option C (RFC 4364
         §10c): the RRs sit outside the forwarding path, so the
         reflected route must keep the originating PE — the true LSP
         endpoint — as its next-hop (and its original VPN label). The
         receiving PE resolves that PE loopback over BGP-LU.

         Required likewise on an EVPN (SAFI 70) session where this
         speaker forwards EVPN between other speakers without being a
         VXLAN tunnel endpoint itself: the receiving PE builds its
         remote FDB from the Type-2 next-hop, so rewriting it points
         the tunnel at a node that cannot decapsulate.

         Honored on the unicast (SAFI 1), VPNv4 (SAFI 128), EVPN
         (SAFI 70), and (for the VPN next-hop) related advertise paths;
         for unicast it preserves the received next-hop on both eBGP and
         iBGP advertisement and takes precedence over next-hop-self.
         Locally-originated routes always advertise with self as the
         next-hop (the originator is the only valid next-hop).";
    }

    container policy {
      ext:sort "40";
      ext:help "Per-family route-policy references";
      description
        "Per-direction route-policy references applied to routes of
         THIS address family. This is the only per-neighbor
         route-policy binding; when a family has no per-family binding
         it falls back to a route-policy inherited from a
         neighbor-group (if any).";
      leaf in {
        ext:help "Inbound route-policy for this family";
        type string;
      }
      leaf out {
        ext:help "Outbound route-policy for this family";
        type string;
      }
    }

    container prefix-set {
      ext:sort "50";
      ext:help "Per-family prefix-set references";
      description
        "Per-direction prefix-set references applied to routes of THIS
         address family. The per-family successor of the (removed)
         peer-wide `neighbor X prefix-set {in,out}`.";
      leaf in {
        ext:help "Inbound prefix-set filter for this family";
        type string;
      }
      leaf out {
        ext:help "Outbound prefix-set filter for this family";
        type string;
      }
    }

    container prefix-sid {
      ext:sort "60";
      ext:help "BGP Prefix-SID across an AS boundary (RFC 8669)";
      description
        "Whether the BGP Prefix-SID attribute (RFC 8669, and the SRv6
         service SIDs of RFC 9252) crosses this session when it is
         external. The SID belongs to the provider's SR domain, so both
         directions are closed unless opened here (RFC 8669 sections 4
         and 5.1, RFC 9252 section 9.2).

         Only the plain unicast families (ipv4, ipv6) use it. VPN
         families keep the attribute: their SIDs are the service the
         session exists for. iBGP sessions are not affected.

         `encapsulation-type srv6` or `srv6-relax` on ipv6 already says
         that the session carries an SRv6 service, so it opens both
         directions for ipv6 as well.";
      leaf send {
        ext:help "Send the Prefix-SID to this external neighbor";
        type boolean;
        default "false";
        description
          "Send the Prefix-SID on routes of this family. A change is
           sent to the neighbor at the end of the commit.";
      }
      leaf accept {
        ext:help "Keep the Prefix-SID received from this external neighbor";
        type boolean;
        default "false";
        description
          "Keep the Prefix-SID on routes of this family received from
           the neighbor. When false the attribute is removed as the
           UPDATE is parsed and the route is kept. The value is read
           when the session starts, so a change applies to the next
           session (use `clear bgp` to apply it now).";
      }
    }

    container send-community {
      ext:sort "70";
      ext:help "Community attributes sent to this neighbor";
      description
        "Which community attributes are sent on routes of this family
         (FRR `neighbor X send-community`). Each kind is sent unless it
         is turned off. The rule runs after the outbound policy, so a
         policy cannot add back a kind that is turned off. A change is
         sent to the neighbor at the end of the commit.";
      leaf standard {
        ext:help "Send COMMUNITIES (RFC 1997)";
        type boolean;
        default "true";
      }
      leaf extended {
        ext:help "Send EXT_COMMUNITIES (RFC 4360, RFC 5701)";
        type boolean;
        default "true";
        description
          "Send the extended communities, the IPv6 Address Specific
           ones included. Turning this off also removes the Route
           Targets of VPN routes.";
      }
      leaf large {
        ext:help "Send LARGE_COMMUNITY (RFC 8092)";
        type boolean;
        default "true";
      }
    }

    container maximum-prefix {
      ext:sort "80";
      ext:help "Limit the prefixes received from this neighbor";
      description
        "Limit how many prefixes of this family the neighbor may send
         (FRR `neighbor X maximum-prefix`). When the count goes above
         `max`, the session is closed with a Cease NOTIFICATION,
         subcode Maximum Number of Prefixes Reached (RFC 4486), and
         the neighbor stays down until `clear bgp`, or until `restart`
         minutes have passed. With `warning-only` a warning is logged
         and the session stays up.

         Only ipv4, ipv6, label-v4, label-v6, vpnv4 and vpnv6 are
         counted; a limit on another family is refused at commit.

         A change applies at once: a limit below the current count
         closes the session. Deleting the limit does not bring back a
         neighbor that is down; `clear bgp` does.";
      leaf max {
        ext:help "Maximum number of prefixes";
        type uint32 {
          range "1..max";
        }
        mandatory true;
      }
      leaf threshold {
        ext:help "Warning threshold in percent of max";
        type uint8 {
          range "1..100";
        }
        units "percent";
        default "75";
        description
          "Log a warning when the count goes above this share of
           `max`.";
      }
      leaf warning-only {
        ext:help "Only log a warning when max is exceeded";
        type boolean;
        default "false";
        description
          "Keep the session when the count goes above `max` and log a
           warning. Cannot be used with a non-zero `restart`.";
      }
      leaf restart {
        ext:help "Minutes before the session may start again";
        type uint16;
        units "minutes";
        description
          "Start the session again this many minutes after it was
           closed for the limit. Absent or 0: stay down until
           `clear bgp`.";
      }
      leaf force {
        ext:help "Count every received prefix, not only accepted ones";
        type boolean;
        default "false";
        description
          "Count every prefix received, before the inbound policy. By
           default only the prefixes that pass the inbound policy and
           the RFC 8212 check are counted.";
      }
    }

    container default-originate {
      ext:sort "90";
      ext:help "Send a default route to this neighbor";
      presence "Send a default route to this neighbor";
      description
        "Send the neighbor a default route, 0.0.0.0/0 or ::/0, with this
         router as next hop (FRR `neighbor X default-originate`). The
         route is not put in the Loc-RIB, so the FIB, the VPN and the
         other neighbors do not get it. As in FRR, the outbound policy
         and ebgp-requires-policy do not apply to it. While it is set,
         a default route from the Loc-RIB is not sent to the neighbor.

         Only ipv4 and ipv6 take it; another family is refused at
         commit. A change is sent to the neighbor at the end of the
         commit.";
    }

    container long-lived-graceful-restart {
      ext:help "Per-family long-lived GR settings (RFC 9494)";
      description
        "Long-Lived Graceful Restart parameters for this family.";
      leaf enabled {
        ext:help "Enable long-lived graceful-restart (RFC 9494)";
        type boolean;
      }
      leaf restart-time {
        ext:help "LLGR stale-retention time (seconds)";
        type uint32;
        units "seconds";
        description
          "Stale-route retention time advertised for this family.
           Deleting only this leaf leaves LLGR enabled with the bare
           marker value — it does not turn the feature off.";
      }
    }
  }
}
